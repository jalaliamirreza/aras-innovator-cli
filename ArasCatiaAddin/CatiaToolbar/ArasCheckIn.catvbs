' Aras Check-In Button
Const ARASCLI_PATH = "D:\Worklab\SAP\Behran\PLM\Codes\v2\aras-innovator-cli\ArasCLI\bin\Debug\ArasCLI.exe"

Sub CATMain()
    Dim fso, shell
    Set fso = CreateObject("Scripting.FileSystemObject")

    If Not fso.FileExists(ARASCLI_PATH) Then
        MsgBox "ArasCLI not found at:" & vbCrLf & ARASCLI_PATH, vbExclamation, "Check In"
        Exit Sub
    End If

    ' Save current document if open and unsaved
    If CATIA.Documents.Count > 0 Then
        Dim doc
        Set doc = CATIA.ActiveDocument

        If doc.Saved = False Then
            Dim result
            result = MsgBox("Document has unsaved changes. Save before check-in?", vbYesNoCancel + vbQuestion, "Check In")
            If result = vbCancel Then Exit Sub
            If result = vbYes Then doc.Save
        End If

        Set doc = Nothing
    End If

    Set shell = CreateObject("WScript.Shell")
    shell.Run """" & ARASCLI_PATH & """ --catia-checkin", 1, False
    Set shell = Nothing
    Set fso = Nothing
End Sub
