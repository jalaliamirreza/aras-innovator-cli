' Aras Login Button
Const ARASCLI_PATH = "D:\Worklab\SAP\Behran\PLM\Codes\v2\aras-innovator-cli\ArasCLI\bin\Debug\ArasCLI.exe"

Sub CATMain()
    Dim fso, shell
    Set fso = CreateObject("Scripting.FileSystemObject")

    If Not fso.FileExists(ARASCLI_PATH) Then
        MsgBox "ArasCLI not found at:" & vbCrLf & ARASCLI_PATH, vbExclamation, "Aras Login"
        Exit Sub
    End If

    Set shell = CreateObject("WScript.Shell")
    shell.Run """" & ARASCLI_PATH & """ --catia-login", 1, False
    Set shell = Nothing
    Set fso = Nothing
End Sub
